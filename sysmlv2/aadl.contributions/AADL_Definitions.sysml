library package AADL_Definitions {

	abstract part def System;

	abstract part def Process;

	abstract part def Thread;
	
	
	abstract port def Data;

	abstract port def Event;

	abstract port def EventData;
	
	
	abstract state def Initial;
	
	abstract state def Complete;
	
	abstract state def Final;
	
	abstract state def Execute;

}
